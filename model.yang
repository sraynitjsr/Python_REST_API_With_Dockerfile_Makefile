module sample-module {
  namespace "http://example.com/sample-module";
  prefix "sm";

  import ietf-inet-types {
    prefix "inet";
  }

  container sample-container {
    leaf sample-leaf {
      type string;
      description "This is a sample leaf node.";
    }
    
    list sample-list {
      key "id";
      description "This is a sample list.";
      
      leaf id {
        type string;
        description "Identifier for the list entry.";
      }
      
      leaf name {
        type string;
        description "Name of the list entry.";
      }
    }
  }
}
